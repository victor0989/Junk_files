# -*- coding: utf-8 -*-
# Macro FreeCAD: Direct Fusion Drive - Ensamblado paramétrico
# Autor: Víctor + Copilot
# Unidades: mm, eje longitudinal = X

import FreeCAD as App
import FreeCADGui as Gui
import Part
import math

doc_name = "Direct_Fusion_Drive"
if App.ActiveDocument is None or App.ActiveDocument.Label != doc_name:
    App.newDocument(doc_name)
doc = App.ActiveDocument

# ============ 
# Parámetros 
# ============
P = {
    # Fuselaje
    "nose_len": 800.0,
    "nose_base_d": 600.0,
    "mid_len": 1400.0,
    "mid_d": 900.0,
    "rear_len": 800.0,
    "rear_d": 1200.0,
    "hull_t": 10.0,
    # Cabina
    "cockpit_w": 900.0,
    "cockpit_h": 400.0,
    "cockpit_l": 600.0,
    "cockpit_x0": 600.0,
    # Ventanas laterales
    "win_w": 600.0,
    "win_h": 250.0,
    "win_th": 20.0,
    "win_y_off": 0.5*(900.0/2.0 - 250.0/2.0),
    "win_z": 0.0,
    # Reactor
    "reactor_d": 800.0,
    "reactor_l": 900.0,
    "reactor_cx": 2600.0,
    "ring_h": 30.0,
    "ring_ro": 420.0,
    "ring_ri": 380.0,
    "ring_n": 6,
    "ring_pitch": 150.0,
    # Coils (solenoides)
    "coil_rect_w": 80.0,
    "coil_rect_h": 80.0,
    "coil_R": 440.0,
    "coil_n": 4,
    "coil_span": 800.0,
    # Blindajes
    "moderator_t": 100.0,
    "moderator_gap": 20.0,
    "moderator_over": 200.0,
    "tungsten_post_t": 10.0,
    # Boquilla magnética
    "nozzle_throat_d": 300.0,
    "nozzle_exit_d": 900.0,
    "nozzle_l": 700.0,
    "nozzle_cx": 2850.0,
    "nozzle_fillet_r": 40.0,
    # Truss soporte boquilla
    "truss_n": 3,
    "truss_tube_w": 80.0,
    "truss_R_attach": 550.0,
    # Tanques
    "tank_d": 300.0,
    "tank_l": 700.0,
    "tank_cx": 1600.0,
    "tank_cy": 300.0,
    "tank_cz": -150.0,
    # Tren de aterrizaje
    "leg_L_fold": 400.0,
    "leg_L_ext": 600.0,
    "leg_foot_d": 180.0,
    "leg_side_x1": 1050.0,
    "leg_side_x2": 1950.0,
    "leg_side_y": 600.0,
    "leg_front_x": 400.0,
    "leg_front_y": 0.0,
    "leg_front_z": -(900.0/2.0) + 50.0,
    # Alas / empenaje
    "wing_root_w": 600.0,
    "wing_tip_w": 150.0,
    "wing_chord": 450.0,
    "fin_h": 400.0,
    "fin_base": 200.0,
    # Radiadores (opcionales)
    "rad_panel_w": 800.0,
    "rad_panel_h": 600.0,
    "rad_panel_n": 5,
}

# Ejes y utilidades
X_AXIS = App.Vector(1,0,0)
Y_AXIS = App.Vector(0,1,0)
Z_AXIS = App.Vector(0,0,1)

def rot_to_x():
    return App.Rotation(Y_AXIS, 90)

def add_obj(shape, label):
    obj = doc.addObject("Part::Feature", label)
    obj.Shape = shape
    return obj

def make_cyl_x(d, L, cx=0.0, cy=0.0, cz=0.0, label="CylX"):
    r = d/2.0
    cyl = Part.makeCylinder(r, L)
    cyl.Placement = App.Placement(App.Vector(cx - L/2.0, cy, cz), rot_to_x())
    return add_obj(cyl, label)

def make_cone_x(d1, d2, L, cx=0.0, cy=0.0, cz=0.0, label="ConeX"):
    r1 = d1/2.0
    r2 = d2/2.0
    cone = Part.makeCone(r1, r2, L)
    cone.Placement = App.Placement(App.Vector(cx - L/2.0, cy, cz), rot_to_x())
    return add_obj(cone, label)

def make_torus_x(R, r, cx=0.0, cy=0.0, cz=0.0, label="TorusX"):
    tor = Part.makeTorus(R, r)
    tor.Placement = App.Placement(App.Vector(cx, cy, cz), rot_to_x())
    return add_obj(tor, label)

def make_box(w, d, h, cx=0.0, cy=0.0, cz=0.0, label="Box"):
    b = Part.makeBox(w, d, h)
    b.Placement = App.Placement(App.Vector(cx - w/2.0, cy - d/2.0, cz - h/2.0), App.Rotation())
    return add_obj(b, label)

def make_hollow_from_offset(outer_shape, t, label="Shell"):
    try:
        inner = outer_shape.makeOffsetShape(-t, 0.01, join=2, fill=True)
        shell = outer_shape.cut(inner)
        return add_obj(shell, label)
    except Exception as e:
        return add_obj(outer_shape, label + "_fallback")

def fillet_between(shpA, shpB, r):
    fused = shpA.fuse(shpB)
    try:
        edges = [e for e in fused.Edges if e.Length > 30 and e.Length < 10000]
        new = fused.makeFillet(r, edges)
        return new
    except Exception:
        return fused

def sweep_rect_around_X(R, rw, rh, cx, cy, cz, ax0, ax1, label="CoilSweep"):
    circ = Part.makeCircle(R, App.Vector(cx,cy,cz), X_AXIS)
    path = Part.Wire([circ])
    p0 = App.Vector(0, -rw/2.0, -rh/2.0)
    p1 = App.Vector(0, rw/2.0, -rh/2.0)
    p2 = App.Vector(0, rw/2.0, rh/2.0)
    p3 = App.Vector(0, -rw/2.0, rh/2.0)
    e1 = Part.makeLine(p0, p1)
    e2 = Part.makeLine(p1, p2)
    e3 = Part.makeLine(p2, p3)
    e4 = Part.makeLine(p3, p0)
    prof = Part.Wire([e1,e2,e3,e4])
    prof.Placement = App.Placement(App.Vector(cx,cy,cz), App.Rotation(X_AXIS,0))
    sweep = Part.Wire(path).makePipeShell([prof], True, True)
    return add_obj(sweep, label)

# =========================
# 1) Fuselaje exterior hueco
# =========================
nose = make_cone_x(P["nose_base_d"], 0.0, P["nose_len"], cx=P["nose_len"]/2.0, label="Nose")
mid = make_cyl_x(P["mid_d"], P["mid_len"], cx=P["nose_len"] + P["mid_len"]/2.0, label="Mid")
rear = make_cyl_x(P["rear_d"], P["rear_len"], cx=P["nose_len"] + P["mid_len"] + P["rear_len"]/2.0, label="Rear")
fuse_fuselage_shape = nose.Shape.fuse(mid.Shape).fuse(rear.Shape)
hull = make_hollow_from_offset(fuse_fuselage_shape, P["hull_t"], label="Hull_Shell")
win1 = make_box(P["win_w"], P["win_th"], P["win_h"], cx=P["cockpit_x0"] + P["cockpit_l"]/2.0, cy=(P["mid_d"]/2.0)-P["win_th"]/2.0, cz=P["win_z"], label="Win_Right")
win2 = make_box(P["win_w"], P["win_th"], P["win_h"], cx=P["cockpit_x0"] + P["cockpit_l"]/2.0, cy=-(P["mid_d"]/2.0)+P["win_th"]/2.0, cz=P["win_z"], label="Win_Left")
# =========================
# 2) Cabina
# =========================
cockpit = make_box(P["cockpit_l"], P["cockpit_w"], P["cockpit_h"],
                   cx=P["cockpit_x0"] + P["cockpit_l"]/2.0,
                   cy=0.0, cz=0.0, label="Cockpit")

# =========================
# 3) Reactor central
# =========================
reactor = make_cyl_x(P["reactor_d"], P["reactor_l"], cx=P["reactor_cx"], label="Reactor")

# =========================
# 4) Anillos magnéticos
# =========================
rings = []
for i in range(P["ring_n"]):
    z = P["reactor_cx"] - P["reactor_l"]/2.0 + i*P["ring_pitch"]
    ring = make_torus_x((P["ring_ro"] + P["ring_ri"])/2.0,
                        (P["ring_ro"] - P["ring_ri"])/2.0,
                        cx=z, label=f"Ring_{i+1}")
    rings.append(ring)

# =========================
# 5) Coils solenoides
# =========================
coils = []
for i in range(P["coil_n"]):
    z = P["reactor_cx"] - P["coil_span"]/2.0 + i*(P["coil_span"]/(P["coil_n"]-1))
    coil = sweep_rect_around_X(P["coil_R"], P["coil_rect_w"], P["coil_rect_h"], cx=0.0, cy=0.0, cz=z,
                               ax0=0.0, ax1=360.0, label=f"Coil_{i+1}")
    coils.append(coil)

# =========================
# 6) Boquilla magnética
# =========================
nozzle = make_cone_x(P["nozzle_throat_d"], P["nozzle_exit_d"], P["nozzle_l"],
                     cx=P["nozzle_cx"], label="Nozzle")
# =========================
# 7) Truss soporte boquilla
# =========================
trusses = []
for i in range(P["truss_n"]):
    angle = i*360.0/P["truss_n"]
    x = P["nozzle_cx"] - P["nozzle_l"]/2.0
    y = P["truss_R_attach"]*math.cos(math.radians(angle))
    z = P["truss_R_attach"]*math.sin(math.radians(angle))
    truss = make_cyl_x(P["truss_tube_w"], P["nozzle_l"]/2.0, cx=x, cy=y, cz=z, label=f"Truss_{i+1}")
    trusses.append(truss)

# =========================
# 8) Tanques de combustible
# =========================
tank1 = make_cyl_x(P["tank_d"], P["tank_l"], cx=P["tank_cx"], cy=P["tank_cy"], cz=P["tank_cz"], label="Tank_1")
tank2 = make_cyl_x(P["tank_d"], P["tank_l"], cx=P["tank_cx"], cy=-P["tank_cy"], cz=P["tank_cz"], label="Tank_2")

# =========================
# 9) Tren de aterrizaje (simplificado)
# =========================
leg1 = make_cyl_x(P["leg_foot_d"], P["leg_L_ext"], cx=P["leg_side_x1"], cy=P["leg_side_y"], cz=-P["mid_d"]/2.0, label="Leg1")
leg2 = make_cyl_x(P["leg_foot_d"], P["leg_L_ext"], cx=P["leg_side_x2"], cy=P["leg_side_y"], cz=-P["mid_d"]/2.0, label="Leg2")
leg3 = make_cyl_x(P["leg_foot_d"], P["leg_L_ext"], cx=P["leg_front_x"], cy=P["leg_front_y"], cz=P["leg_front_z"], label="LegFront")

# =========================
# 10) Alas y empenaje
# =========================
wing_root = make_box(P["wing_chord"], P["wing_root_w"], P["wing_tip_w"],
                     cx=P["mid_len"]/2.0 + P["nose_len"], cy=P["mid_d"]/2.0 + P["wing_tip_w"]/2.0, cz=0.0,
                     label="Wing_Right")
wing_left = make_box(P["wing_chord"], P["wing_root_w"], P["wing_tip_w"],
                     cx=P["mid_len"]/2.0 + P["nose_len"], cy=-(P["mid_d"]/2.0 + P["wing_tip_w"]/2.0), cz=0.0,
                     label="Wing_Left")

fin = make_box(P["fin_base"], P["wing_tip_w"], P["fin_h"],
               cx=P["nose_len"] + P["mid_len"] + P["rear_len"] - P["fin_base"]/2.0,
               cy=0.0, cz=0.0, label="Fin_Vertical")

# =========================
# Refrescar vista
# =========================
doc.recompute()
Gui.SendMsgToActiveView("ViewFit")
