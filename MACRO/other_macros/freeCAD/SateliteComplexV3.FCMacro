import FreeCAD as App
import Part

DOC_NAME = "SATELITE_COMPLEJO_V4"

def get_doc():
    doc = App.ActiveDocument
    if doc is None or doc.Label != DOC_NAME:
        try:
            doc = App.getDocument(DOC_NAME)
        except Exception:
            doc = App.newDocument(DOC_NAME)
    return doc

def new_part(doc, label, parent=None):
    p = doc.addObject("App::Part", label)
    p.Label = label
    if parent:
        parent.addObject(p)
    return p

def add_shape(doc, shape, name, color=None, transparency=0, parent=None):
    obj = doc.addObject("Part::Feature", name)
    obj.Label = name
    obj.Shape = shape
    if color:
        obj.ViewObject.ShapeColor = color
        obj.ViewObject.Transparency = transparency
    if parent:
        parent.addObject(obj)
    return obj

def color_rgb(r,g,b):
    return (r/255.0, g/255.0, b/255.0)

# --- Parámetros geométricos ---
P = {
    'SM_L':1500, 'SM_W':900, 'SM_H':900,
    'PM_D':800,
    'Arm_L':800, 'Arm_D':80,
    'Panel_L':2000, 'Panel_W':900, 'Panel_t':30,
    'HGA_D':600, 'HGA_depth':200,
    'Tank_D':300, 'Tank_L':800,
    'Main_D':200, 'Main_L':300,
    'Mast_L':1200, 'Mast_D':60,
    'Sensor_D':100, 'Sensor_L':200,
    'Star_D':80, 'Star_L':150,
    'Ant_L':400, 'Ant_D':40,
    'Soporte_L':200, 'Soporte_D':60,
    'Bisagra_D':60, 'Bisagra_L':100
}

doc = get_doc()
root = new_part(doc, "SATELITE_COMPLEJO_V4")

# --- 1. ESTRUCTURA PRINCIPAL ---
estructura = new_part(doc, "1_ESTRUCTURA", root)
SM = Part.makeBox(P['SM_L'], P['SM_W'], P['SM_H'])
SM.translate(App.Vector(-P['SM_L']/2, -P['SM_W']/2, -P['SM_H']/2))
add_shape(doc, SM, "Modulo_servicio", color_rgb(255,255,100), 0, estructura)

# --- 2. MODULO PAYLOAD con soporte estructural ---
modulos = new_part(doc, "2_MODULOS", root)
PM = Part.makeSphere(P['PM_D']/2)
PM.translate(App.Vector(P['SM_L']/2 + P['PM_D']/2 + 100, 0, 0))
add_shape(doc, PM, "Payload_Module", color_rgb(160,160,255), 0, modulos)

soporte_payload = Part.makeCylinder(P['Soporte_D']/2, P['Soporte_L'])
soporte_payload.translate(App.Vector(P['SM_L']/2 + 100, 0, -P['Soporte_L']/2))
add_shape(doc, soporte_payload, "Soporte_payload", color_rgb(100,100,100), 0, modulos)

# --- 3. ENERGÍA: Paneles solares articulados con bisagra ---
energia = new_part(doc, "3_ENERGIA", root)
for side in (-1, 1):
    # Brazo solar
    brazo = Part.makeCylinder(P['Arm_D']/2, P['Arm_L'])
    brazo.rotate(App.Vector(0,0,0), App.Vector(1,0,0), 90)
    brazo.translate(App.Vector(0, side*(P['SM_W']/2 + P['Arm_L']/2), 0))
    add_shape(doc, brazo, f"Brazo_solar_{'izq' if side>0 else 'der'}", color_rgb(150,150,150), 0, energia)

    # Bisagra
    bisagra = Part.makeCylinder(P['Bisagra_D']/2, P['Bisagra_L'])
    bisagra.rotate(App.Vector(0,0,0), App.Vector(1,0,0), 90)
    bisagra.translate(App.Vector(0, side*(P['SM_W']/2 + P['Arm_L'] + P['Bisagra_L']/2), 0))
    add_shape(doc, bisagra, f"Bisagra_panel_{'izq' if side>0 else 'der'}", color_rgb(100,100,100), 0, energia)

    # Panel solar
    panel = Part.makeBox(P['Panel_L'], P['Panel_t'], P['Panel_W'])
    panel.translate(App.Vector(-P['Panel_L']/2, side*(P['SM_W']/2 + P['Arm_L'] + P['Bisagra_L'] + P['Panel_t']/2), -P['Panel_W']/2))
    add_shape(doc, panel, f"Panel_solar_{'izq' if side>0 else 'der'}", color_rgb(40,80,200), 20, energia)

# --- 4. COMUNICACIONES: HGA + antenas laterales montadas ---
comms = new_part(doc, "4_COMUNICACIONES", root)
hga_sphere = Part.makeSphere(P['HGA_D']/2)
cut_plane = Part.makeBox(P['HGA_D'], P['HGA_D'], P['HGA_D'])
cut_plane.translate(App.Vector(-P['HGA_D']/2, -P['HGA_D']/2, -P['HGA_depth']))
dish = hga_sphere.cut(cut_plane)
dish.translate(App.Vector(P['SM_L']/2 + 200, -200, 100))
add_shape(doc, dish, "Antena_HGA", color_rgb(220,220,255), 0, comms)

# Antenas laterales sobre mástiles
for side in (-1, 1):
    mastil_ant = Part.makeCylinder(P['Mast_D']/2, P['Mast_L']/2)
    mastil_ant.translate(App.Vector(0, side*(P['SM_W']/2 + 100), P['SM_H']/2))
    add_shape(doc, mastil_ant, f"Mastil_antena_{'izq' if side>0 else 'der'}", color_rgb(100,100,100), 0, comms)

    antena = Part.makeCylinder(P['Ant_D']/2, P['Ant_L'])
    antena.rotate(App.Vector(0,0,0), App.Vector(0,1,0), 90)
    antena.translate(App.Vector(0, side*(P['SM_W']/2 + P['Ant_L']/2 + 100), P['SM_H']/2 + P['Mast_L']/2))
    add_shape(doc, antena, f"Antena_lateral_{'izq' if side>0 else 'der'}", color_rgb(255,200,100), 0, comms)

# --- 5. PROPULSIÓN: Tanques y motores integrados en la base ---
propulsion = new_part(doc, "5_PROPULSION", root)
for side in (-1, 1):
    tank = Part.makeCylinder(P['Tank_D']/2, P['Tank_L'])
    tank.rotate(App.Vector(0,0,0), App.Vector(0,1,0), 90)
    tank.translate(App.Vector(0, side*200, -P['SM_H']/2 - P['Tank_D']/2 - 40))
    add_shape(doc, tank, f"Tanque_{'A' if side>0 else 'B'}", color_rgb(180,200,200), 0, propulsion)

for pos in (-200, 200):
    motor = Part.makeCylinder(P['Main_D']/2, P['Main_L'])
    motor.translate(App.Vector(pos, 0, -P['SM_H']/2 - P['Main_L']))
    add_shape(doc, motor, f"Motor_principal_{pos}", color_rgb(120,120,140), 0, propulsion)

# --- 6. SENSORES: Mástil superior con sensores y star trackers ---
sensores = new_part(doc, "6_SENSORES", root)
mastil = Part.makeCylinder(P['Mast_D']/2, P['Mast_L'])
mastil.translate(App.Vector(P['SM_L']/2, 0, P['SM_H']/2))
add_shape(doc, mastil, "Mastil_superior", color_rgb(100,100,100), 0, sensores)

sensor = Part.makeCylinder(P['Sensor_D']/2, P['Sensor_L'])
sensor.translate(App.Vector(P['SM_L']/2, 0, P['SM_H']/2 + P['Mast_L']))
add_shape(doc, sensor, "Sensor_optico", color_rgb(200,100,100), 0, sensores)

for angle in (45, -45):
    star = Part.makeCylinder(P['Star_D']/2, P['Star_L'])
    star.rotate(App.Vector(0, 0, 0), App.Vector(0, 1, 0), angle)
    star.translate(App.Vector(P['SM_L']/2, 0, P['SM_H']/2 + P['Mast_L'] + 100))
    add_shape(doc, star, f"Star_tracker_{angle}", color_rgb(100, 200, 255), 0, sensores)

# --- Finalizar ---
doc.recompute()
print("SATELITE_COMPLEJO_V4 ensamblado con estructura avanzada, paneles articulados y sensores.")
